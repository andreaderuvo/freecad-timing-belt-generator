# -*- coding: utf-8 -*-
"""
Timing Belt Generator for FreeCAD
Author: andreaderuvo
GitHub: https://github.com/andreaderuvo/freecad-timing-belt-generator
License: CC BY-SA 3.0

Parametric timing belt generator for FreeCAD with accurate tooth profiles.
Supports S3M, GT2, T2.5, HTD, MXL and many more belt types.
"""

import FreeCAD
import Part
import math
from FreeCAD import Base
try:
    import FreeCADGui
except:
    pass

# Belt profile definitions [pitch, back_thickness, belt_width]
TOOTH_PROFILES = {
    "MXL": {"pitch": 2.032, "back_thickness": 0.74, "belt_width": 6.35},
    "T2.5": {"pitch": 2.5, "back_thickness": 0.6, "belt_width": 6},
    "T5": {"pitch": 5, "back_thickness": 1, "belt_width": 10},
    "T10": {"pitch": 10, "back_thickness": 2, "belt_width": 16},
    "GT2_2mm": {"pitch": 2, "back_thickness": 0.76, "belt_width": 6},
    "GT2_3mm": {"pitch": 3, "back_thickness": 1.27, "belt_width": 9},
    "GT2_5mm": {"pitch": 5, "back_thickness": 1.88, "belt_width": 15},
    "AT5": {"pitch": 5, "back_thickness": 1, "belt_width": 10},
    "HTD_3mm": {"pitch": 3, "back_thickness": 1.19, "belt_width": 9},
    "HTD_5mm": {"pitch": 5, "back_thickness": 1.73, "belt_width": 9},
    "HTD_8mm": {"pitch": 8, "back_thickness": 2.64, "belt_width": 30},
    "40DP": {"pitch": 2.073, "back_thickness": 0.74, "belt_width": 4.7625},
    "XL": {"pitch": 5.08, "back_thickness": 1.03, "belt_width": 7.94},
    "L": {"pitch": 9.525, "back_thickness": 1.66, "belt_width": 19.05},
    "S3M": {"pitch": 3, "back_thickness": 1.14, "belt_width": 6}
}

def create_tooth_profile(profile):
    """Create accurate tooth profile for different belt types"""
    
    if profile == "S3M":
        points = [
            Base.Vector(-1.14, -0.6, 0), Base.Vector(-1.14, 0, 0), 
            Base.Vector(-1.065, 0.025, 0), Base.Vector(-0.995, 0.095, 0),
            Base.Vector(-0.945, 0.205, 0), Base.Vector(-0.92, 0.34, 0),
            Base.Vector(-0.615, 0.965, 0), Base.Vector(-0.585, 1.04, 0),
            Base.Vector(-0.54, 1.105, 0), Base.Vector(-0.48, 1.16, 0),
            Base.Vector(-0.41, 1.205, 0), Base.Vector(-0.33, 1.24, 0),
            Base.Vector(-0.245, 1.265, 0), Base.Vector(-0.155, 1.28, 0),
            Base.Vector(-0.065, 1.285, 0), Base.Vector(0, 1.286, 0),
            Base.Vector(0.065, 1.285, 0), Base.Vector(0.155, 1.28, 0),
            Base.Vector(0.245, 1.265, 0), Base.Vector(0.33, 1.24, 0),
            Base.Vector(0.41, 1.205, 0), Base.Vector(0.48, 1.16, 0),
            Base.Vector(0.54, 1.105, 0), Base.Vector(0.585, 1.04, 0),
            Base.Vector(0.615, 0.965, 0), Base.Vector(0.92, 0.34, 0),
            Base.Vector(0.945, 0.205, 0), Base.Vector(0.995, 0.095, 0),
            Base.Vector(1.065, 0.025, 0), Base.Vector(1.14, 0, 0),
            Base.Vector(1.14, -0.6, 0), Base.Vector(-1.14, -0.6, 0)
        ]
    
    elif profile == "GT2_2mm":
        points = [
            Base.Vector(0.747183, -0.5, 0), Base.Vector(0.747183, 0, 0), Base.Vector(0.647876, 0.037218, 0),
            Base.Vector(0.598311, 0.130528, 0), Base.Vector(0.578556, 0.238423, 0), Base.Vector(0.547158, 0.343077, 0),
            Base.Vector(0.504649, 0.443762, 0), Base.Vector(0.451556, 0.53975, 0), Base.Vector(0.358229, 0.636924, 0),
            Base.Vector(0.2484, 0.707276, 0), Base.Vector(0.127259, 0.750044, 0), Base.Vector(0, 0.76447, 0),
            Base.Vector(-0.127259, 0.750044, 0), Base.Vector(-0.2484, 0.707276, 0), Base.Vector(-0.358229, 0.636924, 0),
            Base.Vector(-0.451556, 0.53975, 0), Base.Vector(-0.504797, 0.443762, 0), Base.Vector(-0.547291, 0.343077, 0),
            Base.Vector(-0.578605, 0.238423, 0), Base.Vector(-0.598311, 0.130528, 0), Base.Vector(-0.648009, 0.037218, 0),
            Base.Vector(-0.747183, 0, 0), Base.Vector(-0.747183, -0.5, 0), Base.Vector(0.747183, -0.5, 0)
        ]
    
    elif profile == "T2.5":
        points = [
            Base.Vector(-0.839258, -0.5, 0), Base.Vector(-0.839258, 0, 0), Base.Vector(-0.770246, 0.021652, 0),
            Base.Vector(-0.726369, 0.079022, 0), Base.Vector(-0.529167, 0.620889, 0), Base.Vector(-0.485025, 0.67826, 0),
            Base.Vector(-0.416278, 0.699911, 0), Base.Vector(0.416278, 0.699911, 0), Base.Vector(0.484849, 0.67826, 0),
            Base.Vector(0.528814, 0.620889, 0), Base.Vector(0.726369, 0.079022, 0), Base.Vector(0.770114, 0.021652, 0),
            Base.Vector(0.839258, 0, 0), Base.Vector(0.839258, -0.5, 0), Base.Vector(-0.839258, -0.5, 0)
        ]
    
    elif profile == "MXL":
        points = [
            Base.Vector(-0.660421, -0.5, 0), Base.Vector(-0.660421, 0, 0), Base.Vector(-0.621898, 0.006033, 0),
            Base.Vector(-0.587714, 0.023037, 0), Base.Vector(-0.560056, 0.049424, 0), Base.Vector(-0.541182, 0.083609, 0),
            Base.Vector(-0.417357, 0.424392, 0), Base.Vector(-0.398413, 0.458752, 0), Base.Vector(-0.370649, 0.48514, 0),
            Base.Vector(-0.336324, 0.502074, 0), Base.Vector(-0.297744, 0.508035, 0), Base.Vector(0.297744, 0.508035, 0),
            Base.Vector(0.336268, 0.502074, 0), Base.Vector(0.370452, 0.48514, 0), Base.Vector(0.39811, 0.458752, 0),
            Base.Vector(0.416983, 0.424392, 0), Base.Vector(0.540808, 0.083609, 0), Base.Vector(0.559752, 0.049424, 0),
            Base.Vector(0.587516, 0.023037, 0), Base.Vector(0.621841, 0.006033, 0), Base.Vector(0.660421, 0, 0),
            Base.Vector(0.660421, -0.5, 0), Base.Vector(-0.660421, -0.5, 0)
        ]
    
    elif profile == "HTD_3mm":
        # HTD 3mm profile - rounded teeth for high torque
        points = [
            Base.Vector(-1.135062, -0.5, 0), Base.Vector(-1.135062, 0, 0), Base.Vector(-1.048323, 0.015484, 0),
            Base.Vector(-0.974284, 0.058517, 0), Base.Vector(-0.919162, 0.123974, 0), Base.Vector(-0.889176, 0.206728, 0),
            Base.Vector(-0.81721, 0.579614, 0), Base.Vector(-0.800806, 0.653232, 0), Base.Vector(-0.778384, 0.72416, 0),
            Base.Vector(-0.750244, 0.792137, 0), Base.Vector(-0.716685, 0.856903, 0), Base.Vector(-0.678005, 0.918199, 0),
            Base.Vector(-0.634505, 0.975764, 0), Base.Vector(-0.586483, 1.029338, 0), Base.Vector(-0.534238, 1.078662, 0),
            Base.Vector(-0.47807, 1.123476, 0), Base.Vector(-0.418278, 1.16352, 0), Base.Vector(-0.355162, 1.198533, 0),
            Base.Vector(-0.289019, 1.228257, 0), Base.Vector(-0.22015, 1.25243, 0), Base.Vector(-0.148854, 1.270793, 0),
            Base.Vector(-0.07543, 1.283087, 0), Base.Vector(-0.000176, 1.28905, 0), Base.Vector(0.075081, 1.283145, 0),
            Base.Vector(0.148515, 1.270895, 0), Base.Vector(0.219827, 1.252561, 0), Base.Vector(0.288716, 1.228406, 0),
            Base.Vector(0.354879, 1.19869, 0), Base.Vector(0.418018, 1.163675, 0), Base.Vector(0.477831, 1.123623, 0),
            Base.Vector(0.534017, 1.078795, 0), Base.Vector(0.586276, 1.029452, 0), Base.Vector(0.634307, 0.975857, 0),
            Base.Vector(0.677809, 0.91827, 0), Base.Vector(0.716481, 0.856953, 0), Base.Vector(0.750022, 0.792167, 0),
            Base.Vector(0.778133, 0.724174, 0), Base.Vector(0.800511, 0.653236, 0), Base.Vector(0.816857, 0.579614, 0),
            Base.Vector(0.888471, 0.206728, 0), Base.Vector(0.919014, 0.123974, 0), Base.Vector(0.974328, 0.058517, 0),
            Base.Vector(1.048362, 0.015484, 0), Base.Vector(1.135062, 0, 0), Base.Vector(1.135062, -0.5, 0),
            Base.Vector(-1.135062, -0.5, 0)
        ]
    
    elif profile == "HTD_5mm":
        # HTD 5mm profile - rounded teeth for high torque
        points = [
            Base.Vector(-1.89036, -0.75, 0), Base.Vector(-1.89036, 0, 0), Base.Vector(-1.741168, 0.02669, 0),
            Base.Vector(-1.61387, 0.100806, 0), Base.Vector(-1.518984, 0.21342, 0), Base.Vector(-1.467026, 0.3556, 0),
            Base.Vector(-1.427162, 0.960967, 0), Base.Vector(-1.398568, 1.089602, 0), Base.Vector(-1.359437, 1.213531, 0),
            Base.Vector(-1.310296, 1.332296, 0), Base.Vector(-1.251672, 1.445441, 0), Base.Vector(-1.184092, 1.552509, 0),
            Base.Vector(-1.108081, 1.653042, 0), Base.Vector(-1.024167, 1.746585, 0), Base.Vector(-0.932877, 1.832681, 0),
            Base.Vector(-0.834736, 1.910872, 0), Base.Vector(-0.730271, 1.980701, 0), Base.Vector(-0.62001, 2.041713, 0),
            Base.Vector(-0.504478, 2.09345, 0), Base.Vector(-0.384202, 2.135455, 0), Base.Vector(-0.259708, 2.167271, 0),
            Base.Vector(-0.131524, 2.188443, 0), Base.Vector(-0.000176, 2.198511, 0), Base.Vector(0.131296, 2.188504, 0),
            Base.Vector(0.259588, 2.167387, 0), Base.Vector(0.384174, 2.135616, 0), Base.Vector(0.504527, 2.093648, 0),
            Base.Vector(0.620123, 2.04194, 0), Base.Vector(0.730433, 1.980949, 0), Base.Vector(0.834934, 1.911132, 0),
            Base.Vector(0.933097, 1.832945, 0), Base.Vector(1.024398, 1.746846, 0), Base.Vector(1.108311, 1.653291, 0),
            Base.Vector(1.184308, 1.552736, 0), Base.Vector(1.251865, 1.445639, 0), Base.Vector(1.310455, 1.332457, 0),
            Base.Vector(1.359552, 1.213647, 0), Base.Vector(1.39863, 1.089664, 0), Base.Vector(1.427162, 0.960967, 0),
            Base.Vector(1.467026, 0.3556, 0), Base.Vector(1.518984, 0.21342, 0), Base.Vector(1.61387, 0.100806, 0),
            Base.Vector(1.741168, 0.02669, 0), Base.Vector(1.89036, 0, 0), Base.Vector(1.89036, -0.75, 0),
            Base.Vector(-1.89036, -0.75, 0)
        ]
    
    elif profile == "HTD_8mm":
        # HTD 8mm profile  
        points = [
            Base.Vector(-3.301471, -1, 0), Base.Vector(-3.301471, 0, 0), Base.Vector(-3.16611, 0.012093, 0),
            Base.Vector(-3.038062, 0.047068, 0), Base.Vector(-2.919646, 0.10297, 0), Base.Vector(-2.813182, 0.177844, 0),
            Base.Vector(-2.720989, 0.269734, 0), Base.Vector(-2.645387, 0.376684, 0), Base.Vector(-2.588694, 0.496739, 0),
            Base.Vector(-2.553229, 0.627944, 0), Base.Vector(-2.460801, 1.470025, 0), Base.Vector(-2.411413, 1.691917, 0),
            Base.Vector(-2.343887, 1.905691, 0), Base.Vector(-2.259126, 2.110563, 0), Base.Vector(-2.158035, 2.30575, 0),
            Base.Vector(-2.041518, 2.490467, 0), Base.Vector(-1.910478, 2.66393, 0), Base.Vector(-1.76582, 2.825356, 0),
            Base.Vector(-1.608446, 2.973961, 0), Base.Vector(-1.439261, 3.10896, 0), Base.Vector(-1.259169, 3.22957, 0),
            Base.Vector(-1.069074, 3.335006, 0), Base.Vector(-0.869878, 3.424485, 0), Base.Vector(-0.662487, 3.497224, 0),
            Base.Vector(-0.447804, 3.552437, 0), Base.Vector(-0.226732, 3.589341, 0), Base.Vector(-0.000176, 3.607153, 0),
            Base.Vector(0.226511, 3.589461, 0), Base.Vector(0.447712, 3.552654, 0), Base.Vector(0.66252, 3.497516, 0),
            Base.Vector(0.870027, 3.424833, 0), Base.Vector(1.069329, 3.33539, 0), Base.Vector(1.259517, 3.229973, 0),
            Base.Vector(1.439687, 3.109367, 0), Base.Vector(1.608931, 2.974358, 0), Base.Vector(1.766344, 2.825731, 0),
            Base.Vector(1.911018, 2.664271, 0), Base.Vector(2.042047, 2.490765, 0), Base.Vector(2.158526, 2.305998, 0),
            Base.Vector(2.259547, 2.110755, 0), Base.Vector(2.344204, 1.905821, 0), Base.Vector(2.411591, 1.691983, 0),
            Base.Vector(2.460801, 1.470025, 0), Base.Vector(2.553229, 0.627944, 0), Base.Vector(2.588592, 0.496739, 0),
            Base.Vector(2.645238, 0.376684, 0), Base.Vector(2.720834, 0.269734, 0), Base.Vector(2.81305, 0.177844, 0),
            Base.Vector(2.919553, 0.10297, 0), Base.Vector(3.038012, 0.047068, 0), Base.Vector(3.166095, 0.012093, 0),
            Base.Vector(3.301471, 0, 0), Base.Vector(3.301471, -1, 0), Base.Vector(-3.301471, -1, 0)
        ]
    
    elif profile == "T5":
        # T5 profile
        points = [
            Base.Vector(-1.632126, -0.5, 0), Base.Vector(-1.632126, 0, 0), Base.Vector(-1.568549, 0.004939, 0),
            Base.Vector(-1.507539, 0.019367, 0), Base.Vector(-1.450023, 0.042686, 0), Base.Vector(-1.396912, 0.074224, 0),
            Base.Vector(-1.349125, 0.113379, 0), Base.Vector(-1.307581, 0.159508, 0), Base.Vector(-1.273186, 0.211991, 0),
            Base.Vector(-1.246868, 0.270192, 0), Base.Vector(-1.009802, 0.920362, 0), Base.Vector(-0.983414, 0.978433, 0),
            Base.Vector(-0.949018, 1.030788, 0), Base.Vector(-0.907524, 1.076798, 0), Base.Vector(-0.859829, 1.115847, 0),
            Base.Vector(-0.80682, 1.147314, 0), Base.Vector(-0.749402, 1.170562, 0), Base.Vector(-0.688471, 1.184956, 0),
            Base.Vector(-0.624921, 1.189895, 0), Base.Vector(0.624971, 1.189895, 0), Base.Vector(0.688622, 1.184956, 0),
            Base.Vector(0.749607, 1.170562, 0), Base.Vector(0.807043, 1.147314, 0), Base.Vector(0.860055, 1.115847, 0),
            Base.Vector(0.907754, 1.076798, 0), Base.Vector(0.949269, 1.030788, 0), Base.Vector(0.9837, 0.978433, 0),
            Base.Vector(1.010193, 0.920362, 0), Base.Vector(1.246907, 0.270192, 0), Base.Vector(1.273295, 0.211991, 0),
            Base.Vector(1.307726, 0.159508, 0), Base.Vector(1.349276, 0.113379, 0), Base.Vector(1.397039, 0.074224, 0),
            Base.Vector(1.450111, 0.042686, 0), Base.Vector(1.507589, 0.019367, 0), Base.Vector(1.568563, 0.004939, 0),
            Base.Vector(1.632126, 0, 0), Base.Vector(1.632126, -0.5, 0), Base.Vector(-1.632126, -0.5, 0)
        ]
    
    elif profile == "T10":
        # T10 profile
        points = [
            Base.Vector(-3.06511, -1, 0), Base.Vector(-3.06511, 0, 0), Base.Vector(-2.971998, 0.007239, 0),
            Base.Vector(-2.882718, 0.028344, 0), Base.Vector(-2.79859, 0.062396, 0), Base.Vector(-2.720931, 0.108479, 0),
            Base.Vector(-2.651061, 0.165675, 0), Base.Vector(-2.590298, 0.233065, 0), Base.Vector(-2.539962, 0.309732, 0),
            Base.Vector(-2.501371, 0.394759, 0), Base.Vector(-1.879071, 2.105025, 0), Base.Vector(-1.840363, 2.190052, 0),
            Base.Vector(-1.789939, 2.266719, 0), Base.Vector(-1.729114, 2.334109, 0), Base.Vector(-1.659202, 2.391304, 0),
            Base.Vector(-1.581518, 2.437387, 0), Base.Vector(-1.497376, 2.47144, 0), Base.Vector(-1.408092, 2.492545, 0),
            Base.Vector(-1.314979, 2.499784, 0), Base.Vector(1.314979, 2.499784, 0), Base.Vector(1.408091, 2.492545, 0),
            Base.Vector(1.497371, 2.47144, 0), Base.Vector(1.581499, 2.437387, 0), Base.Vector(1.659158, 2.391304, 0),
            Base.Vector(1.729028, 2.334109, 0), Base.Vector(1.789791, 2.266719, 0), Base.Vector(1.840127, 2.190052, 0),
            Base.Vector(1.878718, 2.105025, 0), Base.Vector(2.501018, 0.394759, 0), Base.Vector(2.539726, 0.309732, 0),
            Base.Vector(2.59015, 0.233065, 0), Base.Vector(2.650975, 0.165675, 0), Base.Vector(2.720887, 0.108479, 0),
            Base.Vector(2.798571, 0.062396, 0), Base.Vector(2.882713, 0.028344, 0), Base.Vector(2.971997, 0.007239, 0),
            Base.Vector(3.06511, 0, 0), Base.Vector(3.06511, -1, 0), Base.Vector(-3.06511, -1, 0)
        ]
    
    elif profile == "AT5":
        # AT5 profile
        points = [
            Base.Vector(-2.134129, -0.75, 0), Base.Vector(-2.134129, 0, 0), Base.Vector(-2.058023, 0.005488, 0),
            Base.Vector(-1.984595, 0.021547, 0), Base.Vector(-1.914806, 0.047569, 0), Base.Vector(-1.849614, 0.082947, 0),
            Base.Vector(-1.789978, 0.127073, 0), Base.Vector(-1.736857, 0.179338, 0), Base.Vector(-1.691211, 0.239136, 0),
            Base.Vector(-1.653999, 0.305859, 0), Base.Vector(-1.349199, 0.959203, 0), Base.Vector(-1.286933, 1.054635, 0),
            Base.Vector(-1.201914, 1.127346, 0), Base.Vector(-1.099961, 1.173664, 0), Base.Vector(-0.986896, 1.18992, 0),
            Base.Vector(0.986543, 1.18992, 0), Base.Vector(1.099614, 1.173664, 0), Base.Vector(1.201605, 1.127346, 0),
            Base.Vector(1.286729, 1.054635, 0), Base.Vector(1.349199, 0.959203, 0), Base.Vector(1.653646, 0.305859, 0),
            Base.Vector(1.690859, 0.239136, 0), Base.Vector(1.73651, 0.179338, 0), Base.Vector(1.789644, 0.127073, 0),
            Base.Vector(1.849305, 0.082947, 0), Base.Vector(1.914539, 0.047569, 0), Base.Vector(1.984392, 0.021547, 0),
            Base.Vector(2.057906, 0.005488, 0), Base.Vector(2.134129, 0, 0), Base.Vector(2.134129, -0.75, 0),
            Base.Vector(-2.134129, -0.75, 0)
        ]
    
    elif profile == "GT2_3mm":
        # GT2 3mm profile
        points = [
            Base.Vector(-1.155171, -0.5, 0), Base.Vector(-1.155171, 0, 0), Base.Vector(-1.065317, 0.016448, 0),
            Base.Vector(-0.989057, 0.062001, 0), Base.Vector(-0.93297, 0.130969, 0), Base.Vector(-0.90364, 0.217664, 0),
            Base.Vector(-0.863705, 0.408181, 0), Base.Vector(-0.800056, 0.591388, 0), Base.Vector(-0.713587, 0.765004, 0),
            Base.Vector(-0.60519, 0.926747, 0), Base.Vector(-0.469751, 1.032548, 0), Base.Vector(-0.320719, 1.108119, 0),
            Base.Vector(-0.162625, 1.153462, 0), Base.Vector(0, 1.168577, 0), Base.Vector(0.162625, 1.153462, 0),
            Base.Vector(0.320719, 1.108119, 0), Base.Vector(0.469751, 1.032548, 0), Base.Vector(0.60519, 0.926747, 0),
            Base.Vector(0.713587, 0.765004, 0), Base.Vector(0.800056, 0.591388, 0), Base.Vector(0.863705, 0.408181, 0),
            Base.Vector(0.90364, 0.217664, 0), Base.Vector(0.932921, 0.130969, 0), Base.Vector(0.988924, 0.062001, 0),
            Base.Vector(1.065168, 0.016448, 0), Base.Vector(1.155171, 0, 0), Base.Vector(1.155171, -0.5, 0),
            Base.Vector(-1.155171, -0.5, 0)
        ]
    
    elif profile == "GT2_5mm":
        # GT2 5mm profile
        points = [
            Base.Vector(-1.975908, -0.75, 0), Base.Vector(-1.975908, 0, 0), Base.Vector(-1.797959, 0.03212, 0),
            Base.Vector(-1.646634, 0.121224, 0), Base.Vector(-1.534534, 0.256431, 0), Base.Vector(-1.474258, 0.426861, 0),
            Base.Vector(-1.446911, 0.570808, 0), Base.Vector(-1.411774, 0.712722, 0), Base.Vector(-1.368964, 0.852287, 0),
            Base.Vector(-1.318597, 0.989189, 0), Base.Vector(-1.260788, 1.123115, 0), Base.Vector(-1.195654, 1.25375, 0),
            Base.Vector(-1.12331, 1.380781, 0), Base.Vector(-1.043869, 1.503892, 0), Base.Vector(-0.935264, 1.612278, 0),
            Base.Vector(-0.817959, 1.706414, 0), Base.Vector(-0.693181, 1.786237, 0), Base.Vector(-0.562151, 1.851687, 0),
            Base.Vector(-0.426095, 1.9027, 0), Base.Vector(-0.286235, 1.939214, 0), Base.Vector(-0.143795, 1.961168, 0),
            Base.Vector(0, 1.9685, 0), Base.Vector(0.143796, 1.961168, 0), Base.Vector(0.286235, 1.939214, 0),
            Base.Vector(0.426095, 1.9027, 0), Base.Vector(0.562151, 1.851687, 0), Base.Vector(0.693181, 1.786237, 0),
            Base.Vector(0.817959, 1.706414, 0), Base.Vector(0.935263, 1.612278, 0), Base.Vector(1.043869, 1.503892, 0),
            Base.Vector(1.123207, 1.380781, 0), Base.Vector(1.195509, 1.25375, 0), Base.Vector(1.26065, 1.123115, 0),
            Base.Vector(1.318507, 0.989189, 0), Base.Vector(1.368956, 0.852287, 0), Base.Vector(1.411872, 0.712722, 0),
            Base.Vector(1.447132, 0.570808, 0), Base.Vector(1.474611, 0.426861, 0), Base.Vector(1.534583, 0.256431, 0),
            Base.Vector(1.646678, 0.121223, 0), Base.Vector(1.798064, 0.03212, 0), Base.Vector(1.975908, 0, 0),
            Base.Vector(1.975908, -0.75, 0), Base.Vector(-1.975908, -0.75, 0)
        ]
    
    elif profile == "XL":
        # XL profile
        points = [
            Base.Vector(-1.525411, -1, 0), Base.Vector(-1.525411, 0, 0), Base.Vector(-1.41777, 0.015495, 0),
            Base.Vector(-1.320712, 0.059664, 0), Base.Vector(-1.239661, 0.129034, 0), Base.Vector(-1.180042, 0.220133, 0),
            Base.Vector(-0.793044, 1.050219, 0), Base.Vector(-0.733574, 1.141021, 0), Base.Vector(-0.652507, 1.210425, 0),
            Base.Vector(-0.555366, 1.254759, 0), Base.Vector(-0.447675, 1.270353, 0), Base.Vector(0.447675, 1.270353, 0),
            Base.Vector(0.555366, 1.254759, 0), Base.Vector(0.652507, 1.210425, 0), Base.Vector(0.733574, 1.141021, 0),
            Base.Vector(0.793044, 1.050219, 0), Base.Vector(1.180042, 0.220133, 0), Base.Vector(1.239711, 0.129034, 0),
            Base.Vector(1.320844, 0.059664, 0), Base.Vector(1.417919, 0.015495, 0), Base.Vector(1.525411, 0, 0),
            Base.Vector(1.525411, -1, 0), Base.Vector(-1.525411, -1, 0)
        ]
    
    elif profile == "L":
        # L profile
        points = [
            Base.Vector(-2.6797, -1, 0), Base.Vector(-2.6797, 0, 0), Base.Vector(-2.600907, 0.006138, 0),
            Base.Vector(-2.525342, 0.024024, 0), Base.Vector(-2.45412, 0.052881, 0), Base.Vector(-2.388351, 0.091909, 0),
            Base.Vector(-2.329145, 0.140328, 0), Base.Vector(-2.277614, 0.197358, 0), Base.Vector(-2.234875, 0.262205, 0),
            Base.Vector(-2.202032, 0.334091, 0), Base.Vector(-1.75224, 1.57093, 0), Base.Vector(-1.719538, 1.642815, 0),
            Base.Vector(-1.676883, 1.707663, 0), Base.Vector(-1.62542, 1.764693, 0), Base.Vector(-1.566256, 1.813112, 0),
            Base.Vector(-1.500512, 1.85214, 0), Base.Vector(-1.4293, 1.880997, 0), Base.Vector(-1.353742, 1.898883, 0),
            Base.Vector(-1.274949, 1.905021, 0), Base.Vector(1.275281, 1.905021, 0), Base.Vector(1.354056, 1.898883, 0),
            Base.Vector(1.429576, 1.880997, 0), Base.Vector(1.500731, 1.85214, 0), Base.Vector(1.566411, 1.813112, 0),
            Base.Vector(1.625508, 1.764693, 0), Base.Vector(1.676919, 1.707663, 0), Base.Vector(1.719531, 1.642815, 0),
            Base.Vector(1.752233, 1.57093, 0), Base.Vector(2.20273, 0.334091, 0), Base.Vector(2.235433, 0.262205, 0),
            Base.Vector(2.278045, 0.197358, 0), Base.Vector(2.329455, 0.140328, 0), Base.Vector(2.388553, 0.091909, 0),
            Base.Vector(2.454233, 0.052881, 0), Base.Vector(2.525384, 0.024024, 0), Base.Vector(2.600904, 0.006138, 0),
            Base.Vector(2.6797, 0, 0), Base.Vector(2.6797, -1, 0), Base.Vector(-2.6797, -1, 0)
        ]
    
    else:
        # Default simple rectangular tooth
        return None
    
    # Create wire from points
    wire = Part.makePolygon(points)
    face = Part.Face(wire)
    return face

def create_timing_belt(tooth_count=72, belt_width=None, pitch=None, profile="S3M", use_accurate_teeth=True):
    """
    Create a timing belt with specified parameters
    """
    
    # Get parameters from profile defaults
    if profile in TOOTH_PROFILES:
        params = TOOTH_PROFILES[profile]
        if pitch is None:
            pitch = params["pitch"]
        if belt_width is None:
            belt_width = params["belt_width"]
        back_thickness = params["back_thickness"]
    else:
        # Default values for unknown profile
        if pitch is None:
            pitch = 3
        if belt_width is None:
            belt_width = 9
        back_thickness = 1.14
    
    tooth_height = 1.2
    tooth_width_ratio = 0.5  # tooth width as ratio of pitch
    
    # Calculate dimensions
    circumference = tooth_count * pitch
    pitch_radius = circumference / (2 * math.pi)
    outer_radius = pitch_radius + back_thickness / 2
    inner_radius = pitch_radius - back_thickness / 2
    
    print(f"Creating {profile} belt: {tooth_count} teeth, {circumference:.1f}mm circumference")
    print(f"Pitch diameter: {pitch_radius * 2:.1f}mm")
    
    # Create belt body (ring)
    outer_cyl = Part.makeCylinder(outer_radius, belt_width)
    inner_cyl = Part.makeCylinder(inner_radius, belt_width)
    belt_body = outer_cyl.cut(inner_cyl)
    
    # Create teeth
    tooth_angle = 360.0 / tooth_count
    
    # Create all teeth positioned radially (pointing toward center)
    teeth_list = []
    for i in range(tooth_count):
        angle = i * tooth_angle
        
        if use_accurate_teeth and profile in ["S3M", "GT2_2mm", "T2.5", "MXL", "HTD_3mm", "HTD_5mm", "HTD_8mm", "T5", "T10", "AT5", "GT2_3mm", "GT2_5mm", "XL", "L"]:
            # Use accurate tooth profile
            tooth_face = create_tooth_profile(profile)
            if tooth_face:
                tooth = tooth_face.extrude(Base.Vector(0, 0, belt_width))
                # Flip 180 degrees so tooth points INWARD
                tooth.rotate(Base.Vector(0,0,0), Base.Vector(0,0,1), 180)
                # Move so the back of tooth aligns with inner radius  
                tooth.translate(Base.Vector(0, inner_radius, 0))
                # Rotate to correct angular position
                tooth.rotate(Base.Vector(0,0,0), Base.Vector(0,0,1), angle - 90)
            else:
                # Fallback to simple tooth
                use_accurate_teeth = False
        else:
            # Use simple rectangular tooth pointing INWARD
            tooth_width = pitch * tooth_width_ratio
            tooth = Part.makeBox(tooth_height, tooth_width, belt_width)
            # Position tooth so it points inward radially
            tooth.translate(Base.Vector(0, -tooth_width/2, 0))  # Changed from -tooth_height to 0
            # Move to inner radius (pointing inward)
            tooth.translate(Base.Vector(inner_radius - tooth_height, 0, 0))  # Subtract tooth_height
            # Rotate to correct angular position
            tooth.rotate(Base.Vector(0,0,0), Base.Vector(0,0,1), angle)
        
        teeth_list.append(tooth)
    
    # Fuse all teeth together first (more efficient)
    if teeth_list:
        teeth_compound = teeth_list[0]
        for t in teeth_list[1:]:
            teeth_compound = teeth_compound.fuse(t)
        
        # Fuse teeth with belt body
        final_belt = belt_body.fuse(teeth_compound)
        
        # Verify result
        if final_belt.isValid():
            bbox = final_belt.BoundBox
            print(f"Belt created successfully!")
            print(f"Dimensions: {bbox.XLength:.1f} x {bbox.YLength:.1f} x {bbox.ZLength:.1f} mm")
            return final_belt
        else:
            print("ERROR: Invalid geometry!")
            return None
    
    return belt_body

def create_belt_gui():
    """Create belt with GUI dialog"""
    try:
        from PySide import QtGui
        
        # Create dialog
        dialog = QtGui.QDialog()
        dialog.setWindowTitle("Timing Belt Generator")
        dialog.resize(350, 250)
        
        layout = QtGui.QVBoxLayout(dialog)
        
        # Profile selection
        profile_label = QtGui.QLabel("Belt Profile:")
        profile_combo = QtGui.QComboBox()
        profile_combo.addItems(sorted(TOOTH_PROFILES.keys()))
        profile_combo.setCurrentText("S3M")
        
        # Tooth count
        teeth_label = QtGui.QLabel("Number of teeth:")
        teeth_spin = QtGui.QSpinBox()
        teeth_spin.setMinimum(10)
        teeth_spin.setMaximum(500)
        teeth_spin.setValue(72)
        
        # Belt width (auto-updated based on profile)
        width_label = QtGui.QLabel("Belt width (mm):")
        width_spin = QtGui.QDoubleSpinBox()
        width_spin.setMinimum(1)
        width_spin.setMaximum(50)
        width_spin.setValue(6)  # Default S3M width
        width_spin.setSingleStep(0.5)
        
        # Update width when profile changes
        def update_width():
            profile = profile_combo.currentText()
            if profile in TOOTH_PROFILES:
                width_spin.setValue(TOOTH_PROFILES[profile]["belt_width"])
        
        profile_combo.currentTextChanged.connect(update_width)
        update_width()  # Set initial value
        
        # Accurate teeth checkbox
        accurate_check = QtGui.QCheckBox("Use accurate tooth profiles")
        accurate_check.setChecked(True)
        
        # Buttons
        button_box = QtGui.QDialogButtonBox(
            QtGui.QDialogButtonBox.Ok | QtGui.QDialogButtonBox.Cancel
        )
        button_box.accepted.connect(dialog.accept)
        button_box.rejected.connect(dialog.reject)
        
        # Add to layout
        layout.addWidget(profile_label)
        layout.addWidget(profile_combo)
        layout.addWidget(teeth_label)
        layout.addWidget(teeth_spin)
        layout.addWidget(width_label)
        layout.addWidget(width_spin)
        layout.addWidget(accurate_check)
        layout.addWidget(button_box)
        
        if dialog.exec_():
            # Create belt
            belt = create_timing_belt(
                tooth_count=teeth_spin.value(),
                belt_width=width_spin.value(),
                profile=profile_combo.currentText(),
                use_accurate_teeth=accurate_check.isChecked()
            )
            
            if belt:
                name = f"{profile_combo.currentText()}_{teeth_spin.value()}T_{width_spin.value()}mm"
                add_to_document(belt, name)
            
    except Exception as e:
        print(f"Error in GUI: {e}")
        # Fallback to simple input
        belt = create_timing_belt()
        if belt:
            add_to_document(belt, "S3M_72T_default")

def add_to_document(shape, name="TimingBelt"):
    """Add shape to FreeCAD document and fit view"""
    doc = FreeCAD.ActiveDocument
    if not doc:
        doc = FreeCAD.newDocument("TimingBelt")
    
    obj = doc.addObject("Part::Feature", name)
    obj.Shape = shape
    doc.recompute()
    
    # Try to fit view
    try:
        FreeCADGui.ActiveDocument.activeView().viewAxonometric()
        FreeCADGui.SendMsgToActiveView("ViewFit")
    except:
        print("Use View > Fit All to see the belt")

# Quick creation functions for S3M
def belt_72():
    """Create standard 72-tooth S3M belt with accurate teeth"""
    belt = create_timing_belt(72, profile="S3M", use_accurate_teeth=True)
    if belt:
        add_to_document(belt, "S3M_72T_accurate")

def belt_90():
    """Create 90-tooth S3M belt with accurate teeth"""
    belt = create_timing_belt(90, belt_width=6.5, profile="S3M", use_accurate_teeth=True)
    if belt:
        add_to_document(belt, "S3M_90T_accurate")

# Quick creation functions for GT2
def gt2_60():
    """Create 60-tooth GT2 2mm belt with accurate teeth"""
    belt = create_timing_belt(60, profile="GT2_2mm", use_accurate_teeth=True)
    if belt:
        add_to_document(belt, "GT2_2mm_60T_accurate")

def gt2_80():
    """Create 80-tooth GT2 2mm belt with accurate teeth"""
    belt = create_timing_belt(80, profile="GT2_2mm", use_accurate_teeth=True)
    if belt:
        add_to_document(belt, "GT2_2mm_80T_accurate")

# Quick creation functions for T2.5
def t25_60():
    """Create 60-tooth T2.5 belt with accurate teeth"""
    belt = create_timing_belt(60, profile="T2.5", use_accurate_teeth=True)
    if belt:
        add_to_document(belt, "T2.5_60T_accurate")

# Quick creation functions for MXL
def mxl_100():
    """Create 100-tooth MXL belt with accurate teeth"""
    belt = create_timing_belt(100, profile="MXL", use_accurate_teeth=True)
    if belt:
        add_to_document(belt, "MXL_100T_accurate")

# Quick creation functions for HTD
def htd3_60():
    """Create 60-tooth HTD 3mm belt with accurate rounded teeth"""
    belt = create_timing_belt(60, profile="HTD_3mm", use_accurate_teeth=True)
    if belt:
        add_to_document(belt, "HTD_3mm_60T_accurate")

def htd5_40():
    """Create 40-tooth HTD 5mm belt with accurate rounded teeth"""
    belt = create_timing_belt(40, profile="HTD_5mm", use_accurate_teeth=True)
    if belt:
        add_to_document(belt, "HTD_5mm_40T_accurate")

# Simple versions for large tooth counts
def belt_207_simple():
    """Create 207-tooth S3M belt with simple teeth (faster)"""
    belt = create_timing_belt(207, belt_width=6.5, profile="S3M", use_accurate_teeth=False)
    if belt:
        add_to_document(belt, "S3M_207T_simple")

# Run when imported
if __name__ == "__main__":
    create_belt_gui()
else:
    print("FreeCAD Timing Belt Generator loaded")
    print("GitHub: https://github.com/andreaderuvo/freecad-timing-belt-generator")
    print("Quick functions:")
    print("  S3M: belt_72(), belt_90(), belt_207_simple()")  
    print("  GT2: gt2_60(), gt2_80()")
    print("  T2.5: t25_60()")
    print("  MXL: mxl_100()")
    print("  HTD: htd3_60(), htd5_40()")
    print("GUI: create_belt_gui()")
    print("Custom: create_timing_belt(teeth, profile='HTD_3mm', use_accurate_teeth=True)")
